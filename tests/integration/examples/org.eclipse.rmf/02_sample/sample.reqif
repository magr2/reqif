# Test data RIF72
Embedded OLE object with multiple representation forms.

# Specification

## R1
- Author: Max Mustermann
- Age: 2
- Priority: 0.8
- Date: 2005-05-17T12:00:00+02:00

### R2
- Author: Hugo
- Age: 10
- Priority: 1.0
- Date: 2005-05-17T12:00:00+01:00
